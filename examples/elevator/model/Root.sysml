package ElevatorNavigation {
    doc /* Load this model directory independently of the project template and BAK. */
    alias systemOfInterest for Elevator::releaseA;

    private import Elevator::*;
    private import CallPanel::*;
    private import CallController::*;
    private import ElevatorContext;
    private import ElevatorUseCases;
    private import ElevatorStakeholderRequirements;
    private import ElevatorProjectLibrary;
    private import ElevatorDocuments;
}
