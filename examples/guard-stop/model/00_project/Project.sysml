package GuardStopProject {
    private import Elan8Method::MethodCore::*;
    part projectInfo : ProjectInfo {
        attribute :>> projectName = "Guard-stop controller";
        attribute :>> notes = "Teaching increment; synthetic observations, no hardware compliance claim.";
    }
}
