package ProjectLibrary {
    doc /* TODO: project-owned shared coordinate frames, interfaces/items and common
         * components. Developed subsystems stay in 60_systems. Import method roles
         * from the external Elan8 library instead of copying their definitions. */
}
