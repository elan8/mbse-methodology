package ProjectLibrary {
    doc /* Project-local reusable definitions (items, ports, quantities). Prefer shared domain libraries when available. */

    // TODO: add project-specific reusable definitions
}
