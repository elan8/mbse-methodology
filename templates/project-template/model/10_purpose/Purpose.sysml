package Purpose {
    doc /* Stakeholders, concerns, context, and top-level needs. See recipes for purpose, context, and concerns. */

    import Elan8::Method::Metadata::*;
    import Elan8::Method::Core::*;
    import ModelingMetadata::*;

    // TODO: add stakeholder needs, concerns, and context parts
}
