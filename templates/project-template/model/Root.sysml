package ProjectNavigation {
    doc /* Load the complete model directory. This package provides navigation only. */
    alias systemOfInterest for Product::candidate;

    private import Product::*;
    private import ProjectContext;
    private import ProjectUseCases;
    private import ProjectStakeholderRequirements;
    private import ProjectLibrary;
    private import ProjectDocuments;
}
