package ProjectViews {
    doc /* Stakeholder views satisfying Elan8 standard viewpoints. */

    private import Views::*;
    import Elan8::Method::Viewpoints::*;

    // TODO: add project-specific views that satisfy Elan8 viewpoints and expose model elements
}
