package Functions {
    doc /*
      System-level functional decomposition: what the system must do as a black
      box, independent of how responsibilities are later allocated to logical or
      physical structure.
    */


    // TODO: add system functions and their inputs/outputs
}
