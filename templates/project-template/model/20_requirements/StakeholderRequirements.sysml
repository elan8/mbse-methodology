package ProjectStakeholderRequirements {
    doc /* TODO: sourced customer/user obligations, owners, rationale and acceptance
         * intent. System requirements belong in each system's Specification package. */
}
