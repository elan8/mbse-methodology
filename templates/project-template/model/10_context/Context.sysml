package Context {
    doc /* Stakeholders, concerns, and operational context. Needs and requirements live in 05_requirements. See docs/workflow.md. */

    private import ModelingMetadata::*;

    // TODO: add concerns and context parts; reference needs and requirements from 05_requirements.
}
