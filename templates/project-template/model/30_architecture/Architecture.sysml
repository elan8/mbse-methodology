package Architecture {
    doc /*
      Structure, interfaces, and allocations.
      Logical part trees are optional; allocate behavior to parts when realizing the design.
    */

    import Elan8::Method::Core::*;

    // TODO: add system structure, interfaces, and allocations
}
