package StakeholderNeeds {
    doc /* Stakeholder-facing needs and desired outcomes. Canonical requirements live in 05_requirements; model-area packages reference them. */

    private import Elan8Method::Metadata::*;

    // TODO: add native requirement usages with optional role metadata and native short names as needed.
    // Capture desired stakeholder outcomes; supplied obligations belong in StakeholderRequirements when needed.
    // Derive measurable system obligations separately, preserving the motivating needs.
}
