package Analysis {
    doc /* Analysis cases, calculations, assumptions, and trade studies. */

    private import Elan8Method::MethodCore::*;

    // TODO: add analysis cases and explicit assumptions
}
