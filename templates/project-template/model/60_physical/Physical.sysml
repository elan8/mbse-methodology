package Physical {
    doc /*
      Selected implementation baseline: hardware, software, mechanics, people,
      and physical interfaces. Allocation from logical responsibilities (or
      directly from functions) to physical parts is the required bridge — not
      mandatory duplication of the logical structure.
    */


    // TODO: add physical parts, interfaces, and allocations
}
