package Behavior {
    doc /* Scenarios, actions, and states. See recipe: model-operational-scenario. */

    import Elan8::Method::Core::*;

    // TODO: add operational scenarios and system behavior
}
