package ProjectViews {
    doc /* Stakeholder views satisfying Elan8 standard viewpoints. */

    private import Views::*;
    private import Elan8Method::Viewpoints::*;

    // TODO: add project-specific views that satisfy Elan8 viewpoints and expose model elements
}
