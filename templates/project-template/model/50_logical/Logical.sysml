package Logical {
    doc /*
      Logical responsibilities and collaborations that realize the functions:
      logical actions/parts, interfaces, and internal allocations. A parallel
      logical-part tree is optional; allocating behavior directly to physical
      parts is a valid tailoring choice (explain the merge in package documentation).
    */


    // TODO: add logical responsibilities, collaborations, and interfaces
}
