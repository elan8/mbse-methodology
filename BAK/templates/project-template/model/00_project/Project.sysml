package Project {
    doc /*
      Project metadata and Elan8 Method tailoring.
      Process ownership and releases stay in Git; engineering meaning lives here.
    */

    doc /*
      NewSystem: replace with the project name and project-specific tailoring notes.
    */

    doc /*
      Conventions:
      - Definitions: PascalCase
      - Usages: camelCase
      - Prefer ISQ/SI quantities
      - Import narrowly from the required standard and domain namespaces
    */
}
