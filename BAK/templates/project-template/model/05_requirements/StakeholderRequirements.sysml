package StakeholderRequirements {
    doc /* Optional canonical home for customer/stakeholder-supplied or agreed obligations. Remove this file and its Root.sysml import when not needed. */

    // TODO: preserve supplied wording/identifier, source reference/revision, and applicable contractual status in documentation.
    // Analyze applicability, conflicts, and ambiguity; record agreed clarifications without silently replacing the source obligation.
    // Add native requirements with explicit subjects and acceptance criteria as appropriate.
    // Derive system requirements only when needed; otherwise reference the canonical supplied requirement directly.
}
