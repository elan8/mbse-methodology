package Elan8 {
    package Method {
        package Core {
        doc /*
          Lightweight Elan8 Method vocabulary: engineering concerns, fixed-stage
          disposition, decisions, assumptions, and risks.

          Process mechanics (PR review, CODEOWNERS, release tags, work increments)
          stay in Git and surrounding tooling. This package encodes engineering
          meaning only.
        */

        import Elan8::Method::Requirements::Name;
        import Elan8::Method::Requirements::Identifier;
        private import ScalarValues::Boolean;

        enum def EngineeringConcernKind {
            enum purpose;
            enum behavior;
            enum architecture;
            enum evidence;
            enum verification;
            enum evolution;
        }

        enum def TailoringProfileKind {
            enum small;
            enum medium;
            enum regulated;
        }

        enum def EngineeringStageKind {
            enum context;
            enum useCases;
            enum capabilities;
            enum functions;
            enum logicalArchitecture;
            enum physicalArchitecture;
            enum verification;
        }

        enum def StageStatusKind {
            enum applicable;
            enum notApplicable;
            enum mergedIntoAnotherStage;
        }

        metadata def EngineeringConcern {
            doc /* Tags a model element with one of the six continuous Elan8 concerns. */
            attribute concern : EngineeringConcernKind;
        }

        metadata def StageDisposition {
            doc /*
              Declares whether a fixed-structure stage package (context, use cases,
              capabilities, functions, logical architecture, physical architecture,
              verification) is populated, deliberately skipped, or merged into a
              neighboring stage for this project. Every stage package carries exactly
              one StageDisposition so tooling can distinguish "empty on purpose" from
              "empty because someone forgot it." Skipped or merged stages require a
              rationale.
            */
            attribute stage : EngineeringStageKind;
            attribute status : StageStatusKind;
            attribute rationale : Name;
            attribute mergedInto : EngineeringStageKind[0..1];
        }

        metadata def DecisionRecord {
            doc /*
              Records an architecture or engineering decision with rationale.
              Approval/workflow status lives in Git (PR merge), not in the model.
            */
            attribute decisionId : Identifier;
            attribute title : Name;
            attribute rationale : Name;
        }

        metadata def Assumption {
            doc /* Explicit assumption that underpins design or analysis. */
            attribute assumptionId : Identifier;
            attribute statement : Name;
            attribute valid : Boolean = true;
        }

        metadata def Risk {
            doc /* Lightweight risk annotation; domain-specific hazard models live elsewhere. */
            attribute riskId : Identifier;
            attribute description : Name;
            attribute severity : Name;
        }

            part def ProjectInfo {
            doc /* Project-level record of how the Elan8 Method is tailored for this model. */
            attribute projectName : Name;
            attribute profile : TailoringProfileKind;
            attribute notes : Name;
            }
        }
    }
}
